# System Requirements Module
Generated by ReqForge — MED — Infusion Platform / System Requirements Module / IEC 62304 Medical Profile

# Specification: System Requirements Module

## REQ-0001: Deliver medication at a programmed rate between
- Requirement Text: The system shall deliver medication at a programmed rate between 0.1 and 999 mL/h.
- Requirement Type: Functional
- Priority: Medium
- Source Traceability: Pasted specification › Infusion Pump System Specification › 4 Functional Requirements › 4.1 Dose Delivery (p.1)
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
## REQ-0002: Support bolus delivery
- Requirement Text: The pump shall support bolus delivery.
- Requirement Type: Functional
- Priority: Medium
- Source Traceability: Pasted specification › Infusion Pump System Specification › 4 Functional Requirements › 4.1 Dose Delivery (p.1)

## REQ-0003: Log every bolus event to the audit
- Requirement Text: The pump shall log every bolus event to the audit trail.
- Requirement Type: Data
- Priority: Medium
- Source Traceability: Pasted specification › Infusion Pump System Specification › 4 Functional Requirements › 4.1 Dose Delivery (p.1)

## REQ-0004: Be fast and user-friendly for clinical staff
- Requirement Text: The device shall be fast and user-friendly for clinical staff.
- Requirement Type: Non-Functional
- Priority: Medium
- Source Traceability: Pasted specification › Infusion Pump System Specification › 4 Functional Requirements › 4.1 Dose Delivery (p.1)

## REQ-0005: The system shall trigger a low-reservoir alarm
- Requirement Text: When the reservoir volume falls below 5 mL, the system shall trigger a low-reservoir alarm.
- Requirement Type: Safety
- Priority: High
- Source Traceability: Pasted specification › Infusion Pump System Specification › 4 Functional Requirements › 4.1 Dose Delivery (p.1)

## REQ-0006: Raise an audible alarm within 2 seconds
- Requirement Text: The system shall raise an audible alarm within 2 seconds of detecting an occlusion.
- Requirement Type: Safety
- Priority: High
- Source Traceability: Pasted specification › Infusion Pump System Specification › 4 Functional Requirements › 4.2 Alarms (p.1)

## REQ-0007: Display all active alarms on the primary
- Requirement Text: The system shall display all active alarms on the primary screen.
- Requirement Type: Functional
- Priority: Medium
- Source Traceability: Pasted specification › Infusion Pump System Specification › 4 Functional Requirements › 4.2 Alarms (p.1)
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
## REQ-0008: Be robust against electrical noise
- Requirement Text: The pump shall be robust against electrical noise.
- Requirement Type: Non-Functional
- Priority: Medium
- Source Traceability: Pasted specification › Infusion Pump System Specification › 4 Functional Requirements › 4.2 Alarms (p.1)

## REQ-0009: Complete startup self-test in under 8 seconds
- Requirement Text: The system shall complete startup self-test in under 8 seconds.
- Requirement Type: Performance
- Priority: Medium
- Source Traceability: Pasted specification › Infusion Pump System Specification › 5 Performance (p.1)
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
## REQ-0010: Deliver medication at an accuracy of plus
- Requirement Text: The system shall deliver medication at an accuracy of plus or minus 5 percent.
- Requirement Type: Performance
- Priority: Medium
- Source Traceability: Pasted specification › Infusion Pump System Specification › 5 Performance (p.1)
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
## REQ-0011: Respond to user input quickly
- Requirement Text: The device shall respond to user input quickly.
- Requirement Type: Functional
- Priority: Low
- Source Traceability: Pasted specification › Infusion Pump System Specification › 5 Performance (p.1)

## REQ-0012: Authenticate every clinician before allowing rate changes
- Requirement Text: The system shall authenticate every clinician before allowing rate changes.
- Requirement Type: Security
- Priority: High
- Source Traceability: Pasted specification › Infusion Pump System Specification › 6 Security (p.1)
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
## REQ-0013: Encrypt all patient data at rest using
- Requirement Text: The system shall encrypt all patient data at rest using AES-256.
- Requirement Type: Security
- Priority: High
- Source Traceability: Pasted specification › Infusion Pump System Specification › 6 Security (p.1)
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
## REQ-0014: Authenticate every clinician before changing the infusion
- Requirement Text: The system shall authenticate every clinician before changing the infusion rate.
- Requirement Type: Security
- Priority: High
- Source Traceability: Pasted specification › Infusion Pump System Specification › 6 Security (p.1)
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
## REQ-0015: Expose an HL7 interface for the hospital
- Requirement Text: The system shall expose an HL7 interface for the hospital information system.
- Requirement Type: Interface
- Priority: Medium
- Source Traceability: Pasted specification › Infusion Pump System Specification › 7 Interface (p.1)
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
## REQ-0016: Provide a USB-C port for service access
- Requirement Text: The system shall provide a USB-C port for service access.
- Requirement Type: Interface
- Priority: Medium
- Source Traceability: Pasted specification › Infusion Pump System Specification › 7 Interface (p.1)
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